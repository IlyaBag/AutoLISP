(defun BG:text-increment (ent inc / props enttype entcontdxf entcont)
;;;  Получает ссылку на объект, содержащий текст с записанным числом, и увеличивает
;;;  число на заданную величину, после чего обновляет объект.
  (setq props      (entget ent)
        entcont    (cdr (assoc 1 props))          ; содержание выбранного объекта
  ) ;_ end setq
  (setq props (subst (cons 1 (itoa (+ (atoi entcont) inc)))
                     (assoc 1 props)
                     props
              ) ;_ end subst
  ) ;_ end setq
  (entmod props)
  (entupd ent)
) ;_ end defun


(defun c:TI ()
  (setq ss  (ssget '((0 . "TEXT,MTEXT")))
        inc (getint "\nВведите шаг увеличения значения:")
        i   0
  ) ;_ end setq
  (while (< i (sslength ss))
    (BG:text-increment (ssname ss i) inc)
    (setq i (1+ i))
  ) ;_ end while
) ;_ end defun



;;; ---------------------------------------------------------------------------

(defun BG:osnap-disable (/ osm)
;;;  Если режим привязок включен - отключает его не сбрасывая настройки привязок.
;;;  Если режим привязок отключен - ничего не меняет.
;;;  Возвращает значение системной переменной OSMODE на момент начала работы функции.
  (setq osm (getvar "osmode"))
  (if (< osm 16384)
    (setvar "osmode" (+ osm 16384))
  ) ;_ end if
  osm
) ;_ end defun


(defun BG:osnap-enable (old_osm)
;;;  Получает числовое значение режима привязки и присваивает его системной
;;;  переменной OSMODE.
  (setvar "osmode" old_osm)
) ;_ end defun

;;; ---------------------------------------------------------------------------


(defun BG:mleader-increment-kludge (ent inc / props entcont osm old_dxf_10 old_dxf_12 new_dxf_10 new_dxf_12)
  (setq props (entget ent))
  (if (= (cdr (assoc 0 props)) "MULTILEADER")
    (progn
      (setq entcont    (cdr (assoc 304 props))
            old_dxf_10 (cdr (assoc 10 props))
            old_dxf_12 (cdr (assoc 12 props))
      ) ;_ end setq
      ;; заменяем текст мультивыноски в списке её свойств
      (setq props (subst (cons 304 (itoa (+ (atoi entcont) inc)))
                         (assoc 304 props)
                         props
                  ) ;_ end subst
      ) ;_ end setq
      ;; обновляем мультивыноску с новым текстом
      (entmod props)
      (entupd ent)
      ;; шевелим мультивыноску чтобы сместилась полка (но не текст)
      (setq osm (BG:osnap-disable))
      (command "_MOVE" ent "" '(0 0) '(1 0)
               "_MOVE" ent "" '(0 0) '(-1 0)
      ) ;_ end command
      (BG:osnap-enable osm)
      ;; получаем обновлённые свойства мультивыноски
      (setq props      (entget ent)
            new_dxf_10 (cdr (assoc 10 props))
      ) ;_ end setq
      ;; смещаем текст мультивыноски на ту же величину, на которую сдвинулась полка
      (setq new_dxf_12
             (list (+ (- (car new_dxf_10) (car old_dxf_10)) (car old_dxf_12))
                   (+ (- (cadr new_dxf_10) (cadr old_dxf_10)) (cadr old_dxf_12))
                   (+ (- (caddr new_dxf_10) (caddr old_dxf_10)) (caddr old_dxf_12))
             ) ;_ end list
      ) ;_ end setq
      ;; меняем в свойствах мультилинии точку вставки текста
      (setq props (subst (cons 12 new_dxf_12)
                         (assoc 12 props)
                         props
                  ) ;_ end subst
      ) ;_ end setq
      ;; окончательно обновляем мультивыноску
      (entmod props)
      (entupd ent)
    ) ;_ end progn
    (princ (strcat "Объект типа " (cdr (assoc 0 props)) " не является мультивыноской"))
  ) ;_ end if
) ;_ end defun


(defun BG:multi-mleader-increment ()
;;;  Изменяет числовое значение в тексте мультивыноски на заданную величину.
  (setq ss  (ssget '((0 . "MULTILEADER")))
        inc (getint "\nВведите шаг увеличения значения:")
        i   0
  ) ;_ end setq
  (while (< i (sslength ss))
    (BG:mleader-increment-kludge (ssname ss i) inc)
    (setq i (1+ i))
  ) ;_ end while
  (princ)
) ;_ end defun





;;;(print (entget (car (entsel))))
;;; мультивыноска до применения функции, после применения (без "_MOVE") и после захода в редактор текста
((-1 . <Имя объекта: 18660a086d0>) (0 . "MULTILEADER") (330 . <Имя объекта: 186654c3700>) (5 . "C6C2D") (100 . "AcDbEntity") (67 . 0) (410 . "Model") (8 . "0") (370 . 15) (100 . "AcDbMLeader") (270 . 2) (300 . "CONTEXT_DATA{") (40 . 1.0) (10 -3468.99 1581.34 0.0) (41 . 30.0) (140 . 0.0) (145 . 5.0) (174 . 5) (175 . 5) (176 . 0) (177 . 0) (290 . 1) (304 . "31") (11 0.0 0.0 1.0) (340 . <Имя объекта: 186654bf1b0>) (12 -3463.99 1617.34 0.0) (13 1.0 0.0 0.0) (42 . 0.0) (43 . 0.0) (44 . 0.0) (45 . 1.0) (170 . 1) (90 . -1073741824) (171 . 1) (172 . 5) (91 . -1073741824) (141 . 0.0) (92 . 0) (291 . 0) (292 . 0) (173 . 0) (293 . 0) (142 . 0.0) (143 . 0.0) (294 . 0) (295 . 0) (296 . 0) (110 -3031.82 1550.39 0.0) (111 1.0 0.0 0.0) (112 0.0 1.0 0.0) (297 . 0) (302 . "LEADER{") (290 . 1) (291 . 1) (10 -3433.99 1581.34 0.0) (11 -1.0 0.0 0.0) (90 . 0) (40 . 1.0) (304 . "LEADER_LINE{") (10 -3400.0 1529.5 0.0) (91 . 0) (170 . 1) (92 . -1056964608) (340 . <Имя объекта: 0>) (171 . -2) (40 . 0.0) (341 . <Имя объекта: 0>) (93 . 0) (305 . "}") (271 . 0) (303 . "}") (272 . 9) (273 . 9) (301 . "}") (340 . <Имя объекта: 186654bf290>) (90 . 1124423020) (170 . 1) (91 . -1073741824) (341 . <Имя объекта: 186654c35c0>) (171 . 15) (290 . 1) (291 . 0) (41 . 1.0) (342 . <Имя объекта: 186654bf2a0>) (42 . 0.0) (172 . 2) (343 . <Имя объекта: 186654bf1b0>) (173 . 5) (95 . 5) (174 . 1) (175 . 2) (92 . -1073741824) (292 . 0) (93 . -1056964608) (10 1.0 1.0 1.0) (43 . 0.0) (176 . 0) (293 . 0) (294 . 0) (178 . 0) (179 . 1) (45 . 1.0) (271 . 0) (272 . 10) (273 . 10) (295 . 1))
((-1 . <Имя объекта: 18660a086d0>) (0 . "MULTILEADER") (330 . <Имя объекта: 186654c3700>) (5 . "C6C2D") (100 . "AcDbEntity") (67 . 0) (410 . "Model") (8 . "0") (370 . 15) (100 . "AcDbMLeader") (270 . 2) (300 . "CONTEXT_DATA{") (40 . 1.0) (10 -3468.99 1581.34 0.0) (41 . 30.0) (140 . 0.0) (145 . 5.0) (174 . 5) (175 . 5) (176 . 0) (177 . 0) (290 . 1) (304 . "29") (11 0.0 0.0 1.0) (340 . <Имя объекта: 186654bf1b0>) (12 -3463.99 1617.34 0.0) (13 1.0 0.0 0.0) (42 . 0.0) (43 . 0.0) (44 . 0.0) (45 . 1.0) (170 . 1) (90 . -1073741824) (171 . 1) (172 . 5) (91 . -1073741824) (141 . 0.0) (92 . 0) (291 . 0) (292 . 0) (173 . 0) (293 . 0) (142 . 0.0) (143 . 0.0) (294 . 0) (295 . 0) (296 . 0) (110 -3031.82 1550.39 0.0) (111 1.0 0.0 0.0) (112 0.0 1.0 0.0) (297 . 0) (302 . "LEADER{") (290 . 1) (291 . 1) (10 -3433.99 1581.34 0.0) (11 -1.0 0.0 0.0) (90 . 0) (40 . 1.0) (304 . "LEADER_LINE{") (10 -3400.0 1529.5 0.0) (91 . 0) (170 . 1) (92 . -1056964608) (340 . <Имя объекта: 0>) (171 . -2) (40 . 0.0) (341 . <Имя объекта: 0>) (93 . 0) (305 . "}") (271 . 0) (303 . "}") (272 . 9) (273 . 9) (301 . "}") (340 . <Имя объекта: 186654bf290>) (90 . 1124423020) (170 . 1) (91 . -1073741824) (341 . <Имя объекта: 186654c35c0>) (171 . 15) (290 . 1) (291 . 0) (41 . 1.0) (342 . <Имя объекта: 186654bf2a0>) (42 . 0.0) (172 . 2) (343 . <Имя объекта: 186654bf1b0>) (173 . 5) (95 . 5) (174 . 1) (175 . 2) (92 . -1073741824) (292 . 0) (93 . -1056964608) (10 1.0 1.0 1.0) (43 . 0.0) (176 . 0) (293 . 0) (294 . 0) (178 . 0) (179 . 1) (45 . 1.0) (271 . 0) (272 . 10) (273 . 10) (295 . 1))
((-1 . <Имя объекта: 18660a086d0>) (0 . "MULTILEADER") (330 . <Имя объекта: 186654c3700>) (5 . "C6C2D") (100 . "AcDbEntity") (67 . 0) (410 . "Model") (8 . "0") (370 . 15) (100 . "AcDbMLeader") (270 . 2) (300 . "CONTEXT_DATA{") (40 . 1.0) (10 -3473.79 1581.34 0.0) (41 . 30.0) (140 . 0.0) (145 . 5.0) (174 . 5) (175 . 5) (176 . 0) (177 . 0) (290 . 1) (304 . "29") (11 0.0 0.0 1.0) (340 . <Имя объекта: 186654bf1b0>) (12 -3468.79 1617.34 0.0) (13 1.0 0.0 0.0) (42 . 0.0) (43 . 0.0) (44 . 0.0) (45 . 1.0) (170 . 1) (90 . -1073741824) (171 . 1) (172 . 5) (91 . -1073741824) (141 . 0.0) (92 . 0) (291 . 0) (292 . 0) (173 . 0) (293 . 0) (142 . 0.0) (143 . 0.0) (294 . 0) (295 . 0) (296 . 0) (110 -3031.82 1550.39 0.0) (111 1.0 0.0 0.0) (112 0.0 1.0 0.0) (297 . 0) (302 . "LEADER{") (290 . 1) (291 . 1) (10 -3433.99 1581.34 0.0) (11 -1.0 0.0 0.0) (90 . 0) (40 . 1.0) (304 . "LEADER_LINE{") (10 -3400.0 1529.5 0.0) (91 . 0) (170 . 1) (92 . -1056964608) (340 . <Имя объекта: 0>) (171 . -2) (40 . 0.0) (341 . <Имя объекта: 0>) (93 . 0) (305 . "}") (271 . 0) (303 . "}") (272 . 9) (273 . 9) (301 . "}") (340 . <Имя объекта: 186654bf290>) (90 . 1124423020) (170 . 1) (91 . -1073741824) (341 . <Имя объекта: 186654c35c0>) (171 . 15) (290 . 1) (291 . 0) (41 . 1.0) (342 . <Имя объекта: 186654bf2a0>) (42 . 0.0) (172 . 2) (343 . <Имя объекта: 186654bf1b0>) (173 . 5) (95 . 5) (174 . 1) (175 . 2) (92 . -1073741824) (292 . 0) (93 . -1056964608) (10 1.0 1.0 1.0) (43 . 0.0) (176 . 0) (293 . 0) (294 . 0) (178 . 0) (179 . 1) (45 . 1.0) (271 . 0) (272 . 10) (273 . 10) (295 . 1))
                                                                                                                                                                                                                                               10 ----4.8-------------                                                                                         304 ------                                                       12 ----4.8-------------
;;; мультивыноска после применения "_MOVE" и без захода в редактор текста
((-1 . <Имя объекта: 18660a086d0>) (0 . "MULTILEADER") (330 . <Имя объекта: 186654c3700>) (5 . "C6C2D") (100 . "AcDbEntity") (67 . 0) (410 . "Model") (8 . "0") (370 . 15) (100 . "AcDbMLeader") (270 . 2) (300 . "CONTEXT_DATA{") (40 . 1.0) (10 -3473.79 1581.34 0.0) (41 . 30.0) (140 . 0.0) (145 . 5.0) (174 . 5) (175 . 5) (176 . 0) (177 . 0) (290 . 1) (304 . "29") (11 0.0 0.0 1.0) (340 . <Имя объекта: 186654bf1b0>) (12 -3463.99 1617.34 0.0) (13 1.0 0.0 0.0) (42 . 0.0) (43 . 0.0) (44 . 0.0) (45 . 1.0) (170 . 1) (90 . -1073741824) (171 . 1) (172 . 5) (91 . -1073741824) (141 . 0.0) (92 . 0) (291 . 0) (292 . 0) (173 . 0) (293 . 0) (142 . 0.0) (143 . 0.0) (294 . 0) (295 . 0) (296 . 0) (110 -3031.82 1550.39 0.0) (111 1.0 0.0 0.0) (112 0.0 1.0 0.0) (297 . 0) (302 . "LEADER{") (290 . 1) (291 . 1) (10 -3433.99 1581.34 0.0) (11 -1.0 0.0 0.0) (90 . 0) (40 . 1.0) (304 . "LEADER_LINE{") (10 -3400.0 1529.5 0.0) (91 . 0) (170 . 1) (92 . -1056964608) (340 . <Имя объекта: 0>) (171 . -2) (40 . 0.0) (341 . <Имя объекта: 0>) (93 . 0) (305 . "}") (271 . 0) (303 . "}") (272 . 9) (273 . 9) (301 . "}") (340 . <Имя объекта: 186654bf290>) (90 . 1124423020) (170 . 1) (91 . -1073741824) (341 . <Имя объекта: 186654c35c0>) (171 . 15) (290 . 1) (291 . 0) (41 . 1.0) (342 . <Имя объекта: 186654bf2a0>) (42 . 0.0) (172 . 2) (343 . <Имя объекта: 186654bf1b0>) (173 . 5) (95 . 5) (174 . 1) (175 . 2) (92 . -1073741824) (292 . 0) (93 . -1056964608) (10 1.0 1.0 1.0) (43 . 0.0) (176 . 0) (293 . 0) (294 . 0) (178 . 0) (179 . 1) (45 . 1.0) (271 . 0) (272 . 10) (273 . 10) (295 . 1))
                                                                                                                                                                                                                                                                                                                                                                                                   (0 . "STYLE")                                                                                                                                                                                                                                                                                                                                                                                                                                                                                                                                                                                                                                                                                                                           (0 . "MLEADERSTYLE")                                                              (0 . "LTYPE")                                                                (0 . "BLOCK_RECORD")                                    (0 . "STYLE")
